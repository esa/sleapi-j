CCSDS-SLE-TRANSFER-SERVICE-CLTU-INCOMING-PDUS
{  iso identified-organization(3) standards-producing-organization(112)
   ccsds(4) space-link-extension(3) sle-transfer-services(1)
   modules(1) forward-cltu-service(21) version-four(4) 
   asn1-incoming-pdus(2)
}

DEFINITIONS
IMPLICIT TAGS
::= BEGIN

IMPORTS     ConditionalTime
,           Credentials
,           Duration
,           IntPosShort
,           InvokeId
,           SlduStatusNotification
FROM CCSDS-SLE-TRANSFER-SERVICE-COMMON-TYPES

            SleScheduleStatusReportInvocation
,           SleStopInvocation
FROM CCSDS-SLE-TRANSFER-SERVICE-COMMON-PDUS
   
            CltuData
,           CltuIdentification
,           ConditionalCltuIdentificationV1
,           CltuParameterName
,           EventInvocationId
FROM CCSDS-SLE-TRANSFER-SERVICE-CLTU-STRUCTURES
   
            SleBindInvocation
,           SlePeerAbort
,           SleUnbindInvocation
FROM CCSDS-SLE-TRANSFER-SERVICE-BIND-TYPES
;

-- =============================================================
-- The first part of the module definition contains the CLTU type
-- that contains all the possible PDUs the provider may receive.
-- =============================================================

CltuUserToProviderPdu         ::=   CHOICE

{  cltuStartInvocation                 [0]   CltuStartInvocation
,  cltuStopInvocation                  [2]   SleStopInvocation
,  cltuScheduleStatusReportInvocation  [4]   SleScheduleStatusReportInvocation
,  cltuGetParameterInvocation          [6]   CltuGetParameterInvocation
,  cltuThrowEventInvocation            [8]   CltuThrowEventInvocation
,  cltuTransferDataInvocation          [10]  CltuTransferDataInvocation
,  cltuBindInvocation                  [100] SleBindInvocation
,  cltuUnbindInvocation                [102] SleUnbindInvocation
,  cltuPeerAbortInvocation             [104] SlePeerAbort
}

-- =============================================================
-- The second part of the module definition contains the types
-- used by the CLTU-PDUs declared in the first part.
-- =============================================================

CltuGetParameterInvocation    ::=   SEQUENCE
{  invokerCredentials               Credentials
,  invokeId                         InvokeId
,  cltuParameter                    CltuParameterName
}

CltuStartInvocation           ::=   SEQUENCE
{  invokerCredentials               Credentials
,  invokeId                         InvokeId
,  firstCltuIdentification          CltuIdentification
}

CltuThrowEventInvocation      ::=   SEQUENCE
{  invokerCredentials               Credentials
,  invokeId                         InvokeId
,  eventInvocationIdentification    EventInvocationId 
,  eventIdentifier                  IntPosShort 
,  eventQualifier                   OCTET STRING (SIZE (1 .. 1024))
}

CltuTransferDataInvocation    ::=   SEQUENCE
{  invokerCredentials               Credentials
,  invokeId                         InvokeId
,  cltuIdentification               CltuIdentification
,  earliestTransmissionTime         ConditionalTime
,  latestTransmissionTime           ConditionalTime
,  delayTime                        Duration
,  slduRadiationNotification        SlduStatusNotification
,  cltuData                         CltuData
}

--!! Changes & Extensions for parallel V1/V2 support - MM 28.05.2004

CltuStartInvocationV1         ::=   SEQUENCE
{  invokerCredentials               Credentials
,  invokeId                         InvokeId
,  firstCltuIdentification          ConditionalCltuIdentificationV1
}

END
