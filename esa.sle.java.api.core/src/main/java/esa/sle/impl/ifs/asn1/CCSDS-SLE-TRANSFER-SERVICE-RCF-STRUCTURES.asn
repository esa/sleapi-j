CCSDS-SLE-TRANSFER-SERVICE-RCF-STRUCTURES
{iso identified-organization(3) standards-producing-organization(112)
    ccsds(4) space-link-extension(3) sle-transfer-services(1)
    modules(1) return-channel-frames-service(13) version-five(5)
    asn1-rcf-structures(1)}

DEFINITIONS
IMPLICIT TAGS
::= BEGIN

EXPORTS     AntennaId
,           CarrierLockStatus
,           DiagnosticRcfGet
,           DiagnosticRcfStart
,           FrameSyncLockStatus
,           GvcId
,           LockStatus
,           Notification
,           RcfGetParameter
,           RcfGetParameterV2To4
,           RcfGetParameterV1 
,           RcfParameterName
,           RcfProductionStatus
,           SymbolLockStatus
;

IMPORTS     DeliveryMode
,           Diagnostics
,           IntPosShort
,           ParameterName
,           Time
    FROM CCSDS-SLE-TRANSFER-SERVICE-COMMON-TYPES
            ReportingCycle
    FROM CCSDS-SLE-TRANSFER-SERVICE-COMMON-PDUS
;

AntennaId                   ::=  --$ Id RcfAntennaId -- CHOICE
{   globalForm                      [0] OBJECT IDENTIFIER
,   localForm                       [1] OCTET STRING (SIZE (1 .. 16))
}

CarrierLockStatus           ::=   LockStatus
(  inLock
|  outOfLock
|  unknown
)


CurrentReportingCycle       ::= --$ Id RcfCurrentReportingCycle -- CHOICE
{   periodicReportingOff            [0] NULL
,   periodicReportingOn             [1] ReportingCycle
}

DiagnosticRcfGet            ::= CHOICE
{   common                          [0] Diagnostics
,   specific                        [1] INTEGER
    {   unknownParameter                    (0)
    }
}

DiagnosticRcfStart          ::= CHOICE
{   common                          [0] Diagnostics
,   specific                        [1] INTEGER
    {   outOfService                        (0)
    ,   unableToComply                      (1)
    ,   invalidStartTime                    (2)
    ,   invalidStopTime                     (3)
    ,   missingTimeValue                    (4)
    ,   invalidGvcId                        (5)
    }
}

FrameSyncLockStatus     ::=   LockStatus
(  inLock
|  outOfLock
|  unknown
)

GvcId                       ::= --$ Id RcfGvcId -- SEQUENCE
{   spacecraftId                   INTEGER (0 .. 1023)   
,   versionNumber                  INTEGER (0 .. 3)
,   vcId                           CHOICE
    {  masterChannel                [0]   NULL
 , virtualChannel                   [1]   VcId
    }
}
-- Notes:
-- The permissible range of the spacecraftId depends on the versionNumber. 
-- PTM and AOS frames are supported. 
-- In case of AOS the permissible range is 0 to 255 (8 bits).
-- In case of PTM the permissible range is 0 to 1023 (10 bits).
GvcIdSet ::= SET OF MasterChannelComposition -- V5_UPDATE_14 --

GvcIdSetV1To4               ::= SEQUENCE OF MasterChannelCompositionV1To4

LockStatus                  ::= --$ Id RcfLockStatus -- INTEGER
{   inLock                          (0)
,   outOfLock                       (1)
,   notInUse                        (2)
,   unknown                         (3)
}

LockStatusReport            ::= --$ Id RcfLockStatusReport -- SEQUENCE
{   time                            Time
,   carrierLockStatus               CarrierLockStatus
,   subcarrierLockStatus            LockStatus
,   symbolSyncLockStatus            SymbolLockStatus
}

MasterChannelComposition    ::= --$ Id RcfMasterChannelComposition -- SEQUENCE
{   spacecraftId                    INTEGER (0 .. 1023)
,   versionNumber                   INTEGER (0 .. 3)
,   mcOrVcList                      CHOICE
    { masterChannel                    [0] NULL
    , vcList                           [1] SET OF VcId 
	}
}
MasterChannelCompositionV1To4 ::= SEQUENCE
{   spacecraftId                    INTEGER (0 .. 1023)
,   versionNumber                   INTEGER (0 .. 3)
,   mcOrVcList CHOICE
	{ masterChannel                [0] NULL
        , vcList                       [1] SEQUENCE OF VcId
        }
}

RequestedGvcId       ::= --$ Id RcfRequestedGvcId -- CHOICE
{  gvcid          [0]   GvcId
,  undefined      [1]   NULL
}


Notification                ::= --$ Id RcfNotification -- CHOICE
{   lossFrameSync                   [0] LockStatusReport
,   productionStatusChange          [1] RcfProductionStatus
,   excessiveDataBacklog            [2] NULL
,   endOfData                       [3] NULL
}

RcfDeliveryMode             ::= DeliveryMode
(   rtnTimelyOnline
|   rtnCompleteOnline
|   rtnOffline
)

RcfGetParameter     ::= CHOICE
{   parBufferSize           [0] SEQUENCE
    { parameterName                 ParameterName (bufferSize)
    , parameterValue                IntPosShort
                                    -- bufferSize in number of invocations
                                    -- that can be held in buffer
    }
,   parDeliveryMode         [1] SEQUENCE
    { parameterName                 ParameterName (deliveryMode)
    , parameterValue                RcfDeliveryMode
    }
,   parLatencyLimit         [2] SEQUENCE
    { parameterName                 ParameterName (latencyLimit)
    , parameterValue                CHOICE
      {   online                [0] IntPosShort
                                    -- latencyLimit in seconds
      ,   offline               [1] NULL
      }
    }
,   parPermittedGvcidSet    [3] SEQUENCE
    { parameterName                 ParameterName (permittedGvcidSet)
    , parameterValue GvcIdSet 
    }
, parReportingCycle         [4] SEQUENCE
	{ parameterName ParameterName (reportingCycle)
	, parameterValue CurrentReportingCycle
	}
, parReqGvcId               [5] SEQUENCE
	{ parameterName ParameterName (requestedGvcid)
	, parameterValue RequestedGvcId
	}
, parReturnTimeout          [6] SEQUENCE
	{ parameterName ParameterName (returnTimeoutPeriod)
	, parameterValue TimeoutPeriod
	}
, parMinReportingCycle      [7] SEQUENCE -- V5_UPDATE_03 --
	{ parameterName ParameterName (minReportingCycle)
	, parameterValue IntPosShort (1 .. 600)
	}
}
RcfGetParameterV2To4 ::= CHOICE
{ parBufferSize             [0] SEQUENCE
	{ parameterName ParameterName (bufferSize)
	, parameterValue IntPosShort
-- bufferSize in number of invocations
-- that can be held in buffer
	}
, parDeliveryMode           [1] SEQUENCE
	{ parameterName ParameterName (deliveryMode)
	, parameterValue RcfDeliveryMode
	}
, parLatencyLimit           [2] SEQUENCE
	{ parameterName ParameterName (latencyLimit)
	, parameterValue CHOICE
		{ online       [0] IntPosShort
-- latencyLimit in seconds
		, offline      [1] NULL
		}
	}
, parPermittedGvcidSet      [3] SEQUENCE
	{ parameterName ParameterName (permittedGvcidSet)
	, parameterValue GvcIdSetV1To4
    }
,   parReportingCycle       [4] SEQUENCE
    { parameterName                 ParameterName (reportingCycle)
    , parameterValue                CurrentReportingCycle
    }
,   parReqGvcId             [5] SEQUENCE
    { parameterName                 ParameterName (requestedGvcid)
    , parameterValue                RequestedGvcId
    }
,   parReturnTimeout        [6] SEQUENCE
    { parameterName                 ParameterName (returnTimeoutPeriod)
    , parameterValue                TimeoutPeriod
    }
}

--!! added for V1 support
RcfGetParameterV1   ::= CHOICE
{   parBufferSize           [0] SEQUENCE
    { parameterName                 ParameterName (bufferSize)
    , parameterValue                IntPosShort
                                    -- bufferSize in number of invocations
                                    -- that can be held in buffer
    }
,   parDeliveryMode         [1] SEQUENCE
    { parameterName                 ParameterName (deliveryMode)
    , parameterValue                RcfDeliveryMode
    }
,   parLatencyLimit         [2] SEQUENCE
    { parameterName                 ParameterName (latencyLimit)
    , parameterValue                CHOICE
      {   online                  [0] IntPosShort
                                      -- latencyLimit in seconds
      ,   offline                 [1] NULL
      }
    }
,   parPermittedGvcidSet    [3] SEQUENCE
    { parameterName                 ParameterName (permittedGvcidSet)
    , parameterValue                GvcIdSetV1To4
    }
,   parReportingCycle       [4] SEQUENCE
    { parameterName                 ParameterName (reportingCycle)
    , parameterValue                CurrentReportingCycle
    }
,   parReqGvcId             [5] SEQUENCE
    { parameterName                 ParameterName (requestedGvcid)
    , parameterValue                GvcId
    }
,   parReturnTimeout        [6] SEQUENCE
    { parameterName                 ParameterName (returnTimeoutPeriod)
    , parameterValue                TimeoutPeriod
    }
}

RcfParameterName            ::= ParameterName
(   bufferSize
|   deliveryMode
|   latencyLimit
|   minReportingCycle 
|   permittedGvcidSet
|   reportingCycle
|   requestedGvcid
|   returnTimeoutPeriod
)

RcfProductionStatus         ::= INTEGER
{   running                         (0)
,   interrupted                     (1)
,   halted                          (2)
}

SymbolLockStatus     ::=   LockStatus
(  inLock
|  outOfLock
|  unknown
)

TimeoutPeriod               ::= INTEGER (1 .. 600)
                                -- measured in seconds

VcId                        ::= INTEGER (0 .. 63)
-- The actual permissible range depends on version number of the associated 
-- GVCID
--

END
