CCSDS-SLE-TRANSFER-SERVICE-CLTU-OUTGOING-PDUS
{  iso identified-organization (3) standards-producing-organization(112)
   ccsds(4) space-link-extension(3) sle-transfer-services(1)
   modules(1) forward-cltu-service(21) version-four(4) 
   asn1-outgoing-pdus(3)
}

DEFINITIONS
IMPLICIT TAGS
::= BEGIN

IMPORTS        ConditionalTime
,              Credentials
,              InvokeId
,              Time
FROM CCSDS-SLE-TRANSFER-SERVICE-COMMON-TYPES

               SleAcknowledgement
,              SleScheduleStatusReportReturn
FROM CCSDS-SLE-TRANSFER-SERVICE-COMMON-PDUS

               SleBindReturn
,              SleUnbindReturn
,              SlePeerAbort
FROM CCSDS-SLE-TRANSFER-SERVICE-BIND-TYPES

               BufferSize
,              CltuGetParameter
,              CltuGetParameterV4
,              CltuGetParameterV1To3
,              CltuIdentification
,              CltuLastProcessed
,              CltuLastOk
,              CltuNotification
,              CltuStatus              
,              DiagnosticCltuGetParameter
,              DiagnosticCltuStart
,              DiagnosticCltuThrowEvent
,              DiagnosticCltuTransferData
,              EventInvocationId
,              NumberOfCltusProcessed
,              NumberOfCltusRadiated
,              NumberOfCltusReceived
,              ProductionStatus
,              UplinkStatus      
FROM CCSDS-SLE-TRANSFER-SERVICE-CLTU-STRUCTURES
;

-- =============================================================
-- The first part of the module definition contains the CLTU type
-- that contains all the possible PDUs the provider may send.
-- =============================================================

CltuProviderToUserPdu         ::=   CHOICE
{  cltuStartReturn                        [1] CltuStartReturn
,  cltuStopReturn                         [3] SleAcknowledgement
,  cltuScheduleStatusReportReturn         [5] SleScheduleStatusReportReturn
,  cltuGetParameterReturn                 [7] CltuGetParameterReturn
,  cltuThrowEventReturn                   [9] CltuThrowEventReturn
,  cltuTransferDataReturn                [11] CltuTransferDataReturn
,  cltuAsyncNotifyInvocation             [12] CltuAsyncNotifyInvocation
,  cltuStatusReportInvocation            [13] CltuStatusReportInvocation
,  cltuBindReturn                       [101] SleBindReturn
,  cltuUnbindReturn                     [103] SleUnbindReturn
,  cltuPeerAbortInvocation              [104] SlePeerAbort
}

-- =============================================================
-- The second part of the module definition contains the types
-- used by the CLTU-PDUs declared in the first part.
-- =============================================================

CltuAsyncNotifyInvocation     ::=   SEQUENCE
{  invokerCredentials               Credentials
,  cltuNotification                 CltuNotification
,  cltuLastProcessed                CltuLastProcessed
,  cltuLastOk                       CltuLastOk
,  productionStatus                 ProductionStatus
,  uplinkStatus                     UplinkStatus
}

CltuGetParameterReturn        ::=   SEQUENCE
{  performerCredentials             Credentials
,  invokeId                         InvokeId
,  result                           CHOICE
   {  positiveResult                   [0]   CltuGetParameter
   ,  negativeResult                   [1]   DiagnosticCltuGetParameter
   }
}

CltuGetParameterReturnV4      ::=   SEQUENCE
{  performerCredentials             Credentials
,  invokeId                         InvokeId
,  result                           CHOICE
   {  positiveResult                   [0]   CltuGetParameterV4
   ,  negativeResult                   [1]   DiagnosticCltuGetParameter
   }
}

--!! Changes & Extensions for parallel V1 to V3 support - LT 19.09.2014
CltuGetParameterReturnV1To3  ::=   SEQUENCE
{  performerCredentials             Credentials
,  invokeId                         InvokeId
,  result                           CHOICE
   {  positiveResult                   [0]   CltuGetParameterV1To3
   ,  negativeResult                   [1]   DiagnosticCltuGetParameter
   }
}

CltuStartReturn               ::=   SEQUENCE
{  performerCredentials             Credentials
,  invokeId                         InvokeId
,  result                           CHOICE
{  positiveResult                      [0]   SEQUENCE
      {  startRadiationTime                  Time
      ,  stopRadiationTime                   ConditionalTime
      }
   ,  negativeResult                   [1]   DiagnosticCltuStart
   }
}

CltuStatusReportInvocation    ::=   SEQUENCE
{  invokerCredentials               Credentials
,  cltuLastProcessed                CltuLastProcessed
,  cltuLastOk                       CltuLastOk
,  cltuProductionStatus             ProductionStatus
,  uplinkStatus                     UplinkStatus
,  numberOfCltusReceived            NumberOfCltusReceived
,  numberOfCltusProcessed           NumberOfCltusProcessed
,  numberOfCltusRadiated            NumberOfCltusRadiated
,  cltuBufferAvailable              BufferSize
}

CltuThrowEventReturn          ::=   SEQUENCE
{  performerCredentials             Credentials
,  invokeId                         InvokeId
,  eventInvocationIdentification    EventInvocationId
,  result                           CHOICE
   {  positiveResult                   [0]   NULL
   ,  negativeResult                   [1]   DiagnosticCltuThrowEvent
   }
}

CltuTransferDataReturn        ::=   SEQUENCE
{  performerCredentials             Credentials
,  invokeId                         InvokeId
,  cltuIdentification               CltuIdentification
,  cltuBufferAvailable              BufferSize
,  result                           CHOICE
   {  positiveResult                      [0]   NULL
   ,  negativeResult                      [1]   DiagnosticCltuTransferData
   }
}

END
